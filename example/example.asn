EXAMPLE DEFINITIONS AUTOMATIC TAGS ::=
BEGIN

Sequence ::= SEQUENCE
{
    null                NULL,
    example1            SubSequence,
    example2            SubSequence OPTIONAL,
    stringList          SEQUENCE (SIZE(3)) OF OCTET STRING(5) OPTIONAL,
    boolExample         BOOLEAN,
    realExample         REAL,
    enumerated          ENUMERATED { enum1, enum2 },
    bitString           BIT STRING { a(0), b(1), c(23) } (SIZE(24)),
    bitString2          BIT STRING (SIZE(8)),
    bitString3          BIT STRING { a(0) } (SIZE(1)),
    octetString         OCTET STRING (SIZE(4)) DEFAULT "abcd",
    octetString2        OCTET STRING (SIZE(4)) DEFAULT "abcd",
    visibleString       VisibleString (SIZE(0..15)),
    utf8String          UTF8String (SIZE(1..5)) DEFAULT "äö",
    optionalSequenceOf  SEQUENCE (SIZE(1..2)) OF SubSequence OPTIONAL,
    date                DATE,
    time                TIME-OF-DAY,
    datetime            UTCTime,
    choiceExample       CHOICE {
        sequence            SubSequence,
        exampleInt          INTEGER (0..255),
        exampleList         SEQUENCE(SIZE(4)) OF INTEGER(0..255)
    } DEFAULT exampleList,
    optionalChoice      CHOICE {
        exampleInt1         INTEGER (0..255),
        exampleInt2         INTEGER (0..255)
    } OPTIONAL,
    ...,
    additional          INTEGER (0..255),
    additionalOptional  INTEGER (0..255) OPTIONAL,
    ...
}

SubSequence ::= SET
{
    member1      INTEGER (0..5000) DEFAULT 1000,
    member2      INTEGER (-100..300),
    enumerated   ENUMERATED { enum1, enum2 } OPTIONAL
}

END
